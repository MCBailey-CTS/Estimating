Language="VBSCRIPT"


Sub GetParams(ByRef myPart As MECMOD.Part, ByRef myProd As ProductStructureTypeLib.Product, ByRef sMatl As String, ByRef myThickness As String, ByRef sPartName As String)
    Dim myParameters As Object 'As Parameters
    myParameters = myPart.Parameters
    Dim myParam As KnowledgewareTypeLib.Parameter
    ' On Error Resume Next
    myParam = myParameters.Item("Material")
    If Err.Number = 0 Then
        sMatl = myParam.ValueAsString
    End If
    ' On Error GoTo 0
    Dim myProduct As ProductStructureTypeLib.Product
    myParameters = myProd.UserRefProperties
    ' On Error Resume Next
    myParam = myParameters.Item("Material")
    If Err.Number = 0 Then
        sMatl = myParam.ValueAsString
    End If
    On Error GoTo 0
    ' On Error Resume Next
    myParam = myParameters.Item("Thickness")
    If Err.Number = 0 Then
        myThickness = myParam.ValueAsString
    End If
    On Error GoTo 0
    sPartName = myProd.Nomenclature
End Sub


'------------------------------------------------------------------------------
' Find the Extents of the Stock body by building Extremums in TEMP body
' Use smartVolume to find PartBody Volume in 'in3'
'Private Sub FindBoundingBoxXYZ(myBodyPart As Part, iBody As Integer, sXLength As String, sYLength As String, sZLength As String, sVolume As String)
Sub FindBoundingBoxXYZ(ByRef myBodyPart As MECMOD.Part, ByRef theStock As Object, ByRef sXLength As String, ByRef sYLength As String, ByRef sZLength As String, ByRef sVolume As String)
    Dim sYMin As Object
    Dim sXMin As Object
    Dim myHBShape As Object

    Dim nShapes As Short
    sXLength = "0.0"
    sYLength = "0.0"
    sZLength = "0.0"
    sVolume = "0.0"
    nShapes = 0
    'UPGRADE_WARNING: Couldn't resolve default property of object CATIA.ActiveDocument. Click for more: 'ms-help://MS.VSCC.v90/dv_commoner/local/redirect.htm?keyword="6A50421D-15FE-4896-8A1B-2EC21E9037B2"'
    mySelection = CATIA.ActiveDocument.Selection
    mySelection.Clear()
    Dim mySel As Object
    Dim sAnswer As String
    'UPGRADE_NOTE: filter was upgraded to filter_Renamed. Click for more: 'ms-help://MS.VSCC.v90/dv_commoner/local/redirect.htm?keyword="A9E4979A-37FA-4718-9994-97DD76ED70A7"'
    Dim filter_Renamed(1) As Object
    'UPGRADE_WARNING: Couldn't resolve default property of object filter_Renamed(0). Click for more: 'ms-help://MS.VSCC.v90/dv_commoner/local/redirect.htm?keyword="6A50421D-15FE-4896-8A1B-2EC21E9037B2"'
    filter_Renamed(0) = "Body"
    'UPGRADE_WARNING: Couldn't resolve default property of object filter_Renamed(1). Click for more: 'ms-help://MS.VSCC.v90/dv_commoner/local/redirect.htm?keyword="6A50421D-15FE-4896-8A1B-2EC21E9037B2"'
    filter_Renamed(1) = "HybridBody"
    If myBodyPart Is Nothing Then
        'do one selection of Part Body
        MsgBox "Select the Part Body, or UNDO to Cancel", MsgBoxStyle.Information, "Part Body Selection"
        mySel = mySelection
        'UPGRADE_WARNING: Couldn't resolve default property of object mySel.SelectElement2. Click for more: 'ms-help://MS.VSCC.v90/dv_commoner/local/redirect.htm?keyword="6A50421D-15FE-4896-8A1B-2EC21E9037B2"'
        sAnswer = mySel.SelectElement2(filter_Renamed, "Select the PartBody, or select UNDO to cancel", True)
        If sAnswer = "Undo" Or sAnswer = "Cancel" Then
            MsgBox "You have chosen to cancel this operation. The program will continue without calculating the size.", MsgBoxStyle.Exclamation, "Skip Size Operation"
            Exit Sub
        End If

        theStock = mySelection.Item(1).Value
        'UPGRADE_WARNING: Couldn't resolve default property of object theStock.Parent. Click for more: 'ms-help://MS.VSCC.v90/dv_commoner/local/redirect.htm?keyword="6A50421D-15FE-4896-8A1B-2EC21E9037B2"'
        myBodyPart = theStock.Parent.Parent
    Else
        'UPGRADE_WARNING: TypeName has a new behavior. Click for more: 'ms-help://MS.VSCC.v90/dv_commoner/local/redirect.htm?keyword="9B7D5ADD-D8FE-4819-A36C-6DEDAF088CC7"'
        If TypeName(theStock) = "HybridBody" Then
            'UPGRADE_WARNING: Couldn't resolve default property of object theStock.HybridShapes. Click for more: 'ms-help://MS.VSCC.v90/dv_commoner/local/redirect.htm?keyword="6A50421D-15FE-4896-8A1B-2EC21E9037B2"'
            nShapes = theStock.HybridShapes.Count
        Else
            'UPGRADE_WARNING: Couldn't resolve default property of object theStock.Shapes. Click for more: 'ms-help://MS.VSCC.v90/dv_commoner/local/redirect.htm?keyword="6A50421D-15FE-4896-8A1B-2EC21E9037B2"'
            nShapes = theStock.Shapes.Count
        End If
        If nShapes = 0 Then
            'do one selection of real Part Body
            MsgBox "Select the Part Body, or UNDO to Cancel", MsgBoxStyle.Information, "Part Body Selection"
            mySel = mySelection
            'UPGRADE_WARNING: Couldn't resolve default property of object mySel.SelectElement2. Click for more: 'ms-help://MS.VSCC.v90/dv_commoner/local/redirect.htm?keyword="6A50421D-15FE-4896-8A1B-2EC21E9037B2"'
            sAnswer = mySel.SelectElement2(filter_Renamed, "Select the PartBody, or select UNDO to cancel", True)
            If sAnswer = "Undo" Or sAnswer = "Cancel" Then
                MsgBox "You have chosen to cancel this operation. The program will continue without calculating the size.", MsgBoxStyle.Exclamation, "Skip Size Operation"
                sXLength = "0.0"
                sYLength = "0.0"
                sZLength = "0.0"
                sVolume = "0.0"
                Exit Sub
            End If

            theStock = mySelection.Item(1).Value
            'UPGRADE_WARNING: Couldn't resolve default property of object theStock.Parent. Click for more: 'ms-help://MS.VSCC.v90/dv_commoner/local/redirect.htm?keyword="6A50421D-15FE-4896-8A1B-2EC21E9037B2"'
            myBodyPart = theStock.Parent.Parent
        End If
    End If

    ' Create reference of the Stock Body (must be Solid Body in NC Geo Part)
    Dim theObjectRef As Object
    ' On Error Resume Next
    'UPGRADE_WARNING: Couldn't resolve default property of object theStock. Click for more: 'ms-help://MS.VSCC.v90/dv_commoner/local/redirect.htm?keyword="6A50421D-15FE-4896-8A1B-2EC21E9037B2"'
    theObjectRef = myBodyPart.CreateReferenceFromObject(theStock)
    If Err.Number <> 0 Then
        MsgBox "Main Body Not Found in " & myBodyPart.Name, MsgBoxStyle.Exclamation, "Body Selection Error"
        Exit Sub
    End If
    On Error GoTo 0

    Dim hCnt As Short
    hCnt = 0
    'UPGRADE_WARNING: TypeName has a new behavior. Click for more: 'ms-help://MS.VSCC.v90/dv_commoner/local/redirect.htm?keyword="9B7D5ADD-D8FE-4819-A36C-6DEDAF088CC7"'
    Dim x As Short
    Dim myHBRef As INFITF.Reference
    Dim myHBShapeFact As MECMOD.Factory
    Dim myHBRef1 As INFITF.Reference
    Dim myHBShapeAssemble As HybridShapeTypeLib.HybridShapeAssemble
    If TypeName(theStock) = "HybridBody" Then
        'UPGRADE_WARNING: Couldn't resolve default property of object theStock.HybridShapes. Click for more: 'ms-help://MS.VSCC.v90/dv_commoner/local/redirect.htm?keyword="6A50421D-15FE-4896-8A1B-2EC21E9037B2"'
        If theStock.HybridShapes.Count = 0 Then
            Exit Sub
        Else
            ' Should be loop thru HybridShapeSurfaceExplicit surfaces - Pre-Select and Join references
            ' Create reference from Join

            x = 0

            Do
                x = x + 1
                'UPGRADE_WARNING: Couldn't resolve default property of object theStock.HybridShapes. Click for more: 'ms-help://MS.VSCC.v90/dv_commoner/local/redirect.htm?keyword="6A50421D-15FE-4896-8A1B-2EC21E9037B2"'
                ' For x = 1 To theStock.HybridShapes.Count
                'UPGRADE_WARNING: Couldn't resolve default property of object theStock.HybridShapes. Click for more: 'ms-help://MS.VSCC.v90/dv_commoner/local/redirect.htm?keyword="6A50421D-15FE-4896-8A1B-2EC21E9037B2"'
                myHBShape = theStock.HybridShapes.Item(x)
                'UPGRADE_WARNING: TypeName has a new behavior. Click for more: 'ms-help://MS.VSCC.v90/dv_commoner/local/redirect.htm?keyword="9B7D5ADD-D8FE-4819-A36C-6DEDAF088CC7"'
                If TypeName(myHBShape) = "HybridShapeSurfaceExplicit" Then
                    'UPGRADE_WARNING: Couldn't resolve default property of object myHBShape.Name. Click for more: 'ms-help://MS.VSCC.v90/dv_commoner/local/redirect.htm?keyword="6A50421D-15FE-4896-8A1B-2EC21E9037B2"'
                    'UPGRADE_WARNING: TypeName has a new behavior. Click for more: 'ms-help://MS.VSCC.v90/dv_commoner/local/redirect.htm?keyword="9B7D5ADD-D8FE-4819-A36C-6DEDAF088CC7"'

                    hCnt = hCnt + 1
                    'UPGRADE_WARNING: Couldn't resolve default property of object myHBShape. Click for more: 'ms-help://MS.VSCC.v90/dv_commoner/local/redirect.htm?keyword="6A50421D-15FE-4896-8A1B-2EC21E9037B2"'
                    myHBRef = myBodyPart.CreateReferenceFromObject(myHBShape)
                    If hCnt = 1 Then
                        myHBShapeFact = myBodyPart.HybridShapeFactory
                        'UPGRADE_WARNING: Couldn't resolve default property of object myHBShape. Click for more: 'ms-help://MS.VSCC.v90/dv_commoner/local/redirect.htm?keyword="6A50421D-15FE-4896-8A1B-2EC21E9037B2"'
                        myHBRef1 = myBodyPart.CreateReferenceFromObject(myHBShape)
                    ElseIf hCnt = 2 Then
                        'UPGRADE_WARNING: Couldn't resolve default property of object myHBShapeFact.AddNewJoin. Click for more: 'ms-help://MS.VSCC.v90/dv_commoner/local/redirect.htm?keyword="6A50421D-15FE-4896-8A1B-2EC21E9037B2"'
                        myHBShapeAssemble = myHBShapeFact.AddNewJoin(myHBRef1, myHBRef)
                    Else
                        myHBShapeAssemble.AddElement(myHBRef)
                    End If

                End If
                ' Next

            Loop While x <= theStock.HybridShapes.Count


            If hCnt > 1 Then
                myHBShapeAssemble.SetConnex(0)
                myHBShapeAssemble.SetManifold(0)
                myHBShapeAssemble.SetSimplify(0)
                myHBShapeAssemble.SetSuppressMode(0)
                myHBShapeAssemble.SetDeviation(0.001)
                myHBShapeAssemble.SetAngularToleranceMode(0)
                myHBShapeAssemble.SetAngularTolerance(0.5)
                myHBShapeAssemble.SetFederationPropagation(0)
                'UPGRADE_WARNING: Couldn't resolve default property of object theStock.AppendHybridShape. Click for more: 'ms-help://MS.VSCC.v90/dv_commoner/local/redirect.htm?keyword="6A50421D-15FE-4896-8A1B-2EC21E9037B2"'
                theStock.AppendHybridShape(myHBShapeAssemble)
                'UPGRADE_WARNING: Couldn't resolve default property of object myHBShapeAssemble. Click for more: 'ms-help://MS.VSCC.v90/dv_commoner/local/redirect.htm?keyword="6A50421D-15FE-4896-8A1B-2EC21E9037B2"'
                myBodyPart.InWorkObject = myHBShapeAssemble
                myBodyPart.Update()
                'UPGRADE_WARNING: Couldn't resolve default property of object myHBShapeAssemble. Click for more: 'ms-help://MS.VSCC.v90/dv_commoner/local/redirect.htm?keyword="6A50421D-15FE-4896-8A1B-2EC21E9037B2"'
                theObjectRef = myBodyPart.CreateReferenceFromObject(myHBShapeAssemble)
            Else
                'UPGRADE_WARNING: Couldn't resolve default property of object theStock.HybridShapes. Click for more: 'ms-help://MS.VSCC.v90/dv_commoner/local/redirect.htm?keyword="6A50421D-15FE-4896-8A1B-2EC21E9037B2"'
                theObjectRef = myBodyPart.CreateReferenceFromObject(theStock.HybridShapes.Item(1))
            End If
        End If
    Else
        'UPGRADE_WARNING: Couldn't resolve default property of object theStock.Shapes. Click for more: 'ms-help://MS.VSCC.v90/dv_commoner/local/redirect.htm?keyword="6A50421D-15FE-4896-8A1B-2EC21E9037B2"'
        If theStock.Shapes.Count = 0 Then
            Exit Sub
        End If
    End If

    ' Initialize the mins,maxs to impossible values
    Dim mins(2) As Object
    Dim maxs(2) As Object
    'UPGRADE_WARNING: Couldn't resolve default property of object mins(0). Click for more: 'ms-help://MS.VSCC.v90/dv_commoner/local/redirect.htm?keyword="6A50421D-15FE-4896-8A1B-2EC21E9037B2"'
    mins(0) = 100000
    'UPGRADE_WARNING: Couldn't resolve default property of object mins(1). Click for more: 'ms-help://MS.VSCC.v90/dv_commoner/local/redirect.htm?keyword="6A50421D-15FE-4896-8A1B-2EC21E9037B2"'
    mins(1) = 100000
    'UPGRADE_WARNING: Couldn't resolve default property of object mins(2). Click for more: 'ms-help://MS.VSCC.v90/dv_commoner/local/redirect.htm?keyword="6A50421D-15FE-4896-8A1B-2EC21E9037B2"'
    mins(2) = 100000
    'UPGRADE_WARNING: Couldn't resolve default property of object maxs(0). Click for more: 'ms-help://MS.VSCC.v90/dv_commoner/local/redirect.htm?keyword="6A50421D-15FE-4896-8A1B-2EC21E9037B2"'
    maxs(0) = -100000
    'UPGRADE_WARNING: Couldn't resolve default property of object maxs(1). Click for more: 'ms-help://MS.VSCC.v90/dv_commoner/local/redirect.htm?keyword="6A50421D-15FE-4896-8A1B-2EC21E9037B2"'
    maxs(1) = -100000
    'UPGRADE_WARNING: Couldn't resolve default property of object maxs(2). Click for more: 'ms-help://MS.VSCC.v90/dv_commoner/local/redirect.htm?keyword="6A50421D-15FE-4896-8A1B-2EC21E9037B2"'
    maxs(2) = -100000

    ' Add a temporary body for points (TEMP body can be deleted)
    Dim tempBody As Object
    tempBody = myBodyPart.HybridBodies.Add()
    'UPGRADE_WARNING: Couldn't resolve default property of object tempBody.Name. Click for more: 'ms-help://MS.VSCC.v90/dv_commoner/local/redirect.htm?keyword="6A50421D-15FE-4896-8A1B-2EC21E9037B2"'
    tempBody.Name = "TEMP"

    'get the HybridShapeFactory
    Dim theHSF As HybridShapeTypeLib.HybridShapeFactory
    theHSF = myBodyPart.HybridShapeFactory

    ' Evalute the Axis System Directions
    Dim originCoord(2) As Object
    'UPGRADE_WARNING: Couldn't resolve default property of object originCoord(0). Click for more: 'ms-help://MS.VSCC.v90/dv_commoner/local/redirect.htm?keyword="6A50421D-15FE-4896-8A1B-2EC21E9037B2"'
    originCoord(0) = 0
    'UPGRADE_WARNING: Couldn't resolve default property of object originCoord(1). Click for more: 'ms-help://MS.VSCC.v90/dv_commoner/local/redirect.htm?keyword="6A50421D-15FE-4896-8A1B-2EC21E9037B2"'
    originCoord(1) = 0
    'UPGRADE_WARNING: Couldn't resolve default property of object originCoord(2). Click for more: 'ms-help://MS.VSCC.v90/dv_commoner/local/redirect.htm?keyword="6A50421D-15FE-4896-8A1B-2EC21E9037B2"'
    originCoord(2) = 0

    Dim XAxisCoord(2) As Object
    'UPGRADE_WARNING: Couldn't resolve default property of object XAxisCoord(0). Click for more: 'ms-help://MS.VSCC.v90/dv_commoner/local/redirect.htm?keyword="6A50421D-15FE-4896-8A1B-2EC21E9037B2"'
    XAxisCoord(0) = 1
    'UPGRADE_WARNING: Couldn't resolve default property of object XAxisCoord(1). Click for more: 'ms-help://MS.VSCC.v90/dv_commoner/local/redirect.htm?keyword="6A50421D-15FE-4896-8A1B-2EC21E9037B2"'
    XAxisCoord(1) = 0
    'UPGRADE_WARNING: Couldn't resolve default property of object XAxisCoord(2). Click for more: 'ms-help://MS.VSCC.v90/dv_commoner/local/redirect.htm?keyword="6A50421D-15FE-4896-8A1B-2EC21E9037B2"'
    XAxisCoord(2) = 0

    Dim YAxisCoord(2) As Object
    'UPGRADE_WARNING: Couldn't resolve default property of object YAxisCoord(0). Click for more: 'ms-help://MS.VSCC.v90/dv_commoner/local/redirect.htm?keyword="6A50421D-15FE-4896-8A1B-2EC21E9037B2"'
    YAxisCoord(0) = 0
    'UPGRADE_WARNING: Couldn't resolve default property of object YAxisCoord(1). Click for more: 'ms-help://MS.VSCC.v90/dv_commoner/local/redirect.htm?keyword="6A50421D-15FE-4896-8A1B-2EC21E9037B2"'
    YAxisCoord(1) = 1
    'UPGRADE_WARNING: Couldn't resolve default property of object YAxisCoord(2). Click for more: 'ms-help://MS.VSCC.v90/dv_commoner/local/redirect.htm?keyword="6A50421D-15FE-4896-8A1B-2EC21E9037B2"'
    YAxisCoord(2) = 0

    Dim ZAxisCoord(2) As Object
    'UPGRADE_WARNING: Couldn't resolve default property of object ZAxisCoord(0). Click for more: 'ms-help://MS.VSCC.v90/dv_commoner/local/redirect.htm?keyword="6A50421D-15FE-4896-8A1B-2EC21E9037B2"'
    ZAxisCoord(0) = 0
    'UPGRADE_WARNING: Couldn't resolve default property of object ZAxisCoord(1). Click for more: 'ms-help://MS.VSCC.v90/dv_commoner/local/redirect.htm?keyword="6A50421D-15FE-4896-8A1B-2EC21E9037B2"'
    ZAxisCoord(1) = 0
    'UPGRADE_WARNING: Couldn't resolve default property of object ZAxisCoord(2). Click for more: 'ms-help://MS.VSCC.v90/dv_commoner/local/redirect.htm?keyword="6A50421D-15FE-4896-8A1B-2EC21E9037B2"'
    ZAxisCoord(2) = 1

    ' Make directions for X Y and Z
    Dim theXDir As Object
    'UPGRADE_WARNING: Couldn't resolve default property of object XAxisCoord(2). Click for more: 'ms-help://MS.VSCC.v90/dv_commoner/local/redirect.htm?keyword="6A50421D-15FE-4896-8A1B-2EC21E9037B2"'
    'UPGRADE_WARNING: Couldn't resolve default property of object originCoord(2). Click for more: 'ms-help://MS.VSCC.v90/dv_commoner/local/redirect.htm?keyword="6A50421D-15FE-4896-8A1B-2EC21E9037B2"'
    'UPGRADE_WARNING: Couldn't resolve default property of object XAxisCoord(1). Click for more: 'ms-help://MS.VSCC.v90/dv_commoner/local/redirect.htm?keyword="6A50421D-15FE-4896-8A1B-2EC21E9037B2"'
    'UPGRADE_WARNING: Couldn't resolve default property of object originCoord(1). Click for more: 'ms-help://MS.VSCC.v90/dv_commoner/local/redirect.htm?keyword="6A50421D-15FE-4896-8A1B-2EC21E9037B2"'
    'UPGRADE_WARNING: Couldn't resolve default property of object XAxisCoord(0). Click for more: 'ms-help://MS.VSCC.v90/dv_commoner/local/redirect.htm?keyword="6A50421D-15FE-4896-8A1B-2EC21E9037B2"'
    'UPGRADE_WARNING: Couldn't resolve default property of object originCoord(). Click for more: 'ms-help://MS.VSCC.v90/dv_commoner/local/redirect.htm?keyword="6A50421D-15FE-4896-8A1B-2EC21E9037B2"'
    theXDir = theHSF.AddNewDirectionByCoord(originCoord(0) - XAxisCoord(0), originCoord(1) - XAxisCoord(1), originCoord(2) - XAxisCoord(2))

    Dim theYDir As Object
    'UPGRADE_WARNING: Couldn't resolve default property of object YAxisCoord(2). Click for more: 'ms-help://MS.VSCC.v90/dv_commoner/local/redirect.htm?keyword="6A50421D-15FE-4896-8A1B-2EC21E9037B2"'
    'UPGRADE_WARNING: Couldn't resolve default property of object originCoord(2). Click for more: 'ms-help://MS.VSCC.v90/dv_commoner/local/redirect.htm?keyword="6A50421D-15FE-4896-8A1B-2EC21E9037B2"'
    'UPGRADE_WARNING: Couldn't resolve default property of object YAxisCoord(1). Click for more: 'ms-help://MS.VSCC.v90/dv_commoner/local/redirect.htm?keyword="6A50421D-15FE-4896-8A1B-2EC21E9037B2"'
    'UPGRADE_WARNING: Couldn't resolve default property of object originCoord(1). Click for more: 'ms-help://MS.VSCC.v90/dv_commoner/local/redirect.htm?keyword="6A50421D-15FE-4896-8A1B-2EC21E9037B2"'
    'UPGRADE_WARNING: Couldn't resolve default property of object YAxisCoord(0). Click for more: 'ms-help://MS.VSCC.v90/dv_commoner/local/redirect.htm?keyword="6A50421D-15FE-4896-8A1B-2EC21E9037B2"'
    'UPGRADE_WARNING: Couldn't resolve default property of object originCoord(). Click for more: 'ms-help://MS.VSCC.v90/dv_commoner/local/redirect.htm?keyword="6A50421D-15FE-4896-8A1B-2EC21E9037B2"'
    theYDir = theHSF.AddNewDirectionByCoord(originCoord(0) - YAxisCoord(0), originCoord(1) - YAxisCoord(1), originCoord(2) - YAxisCoord(2))

    Dim theZDir As Object
    'UPGRADE_WARNING: Couldn't resolve default property of object ZAxisCoord(2). Click for more: 'ms-help://MS.VSCC.v90/dv_commoner/local/redirect.htm?keyword="6A50421D-15FE-4896-8A1B-2EC21E9037B2"'
    'UPGRADE_WARNING: Couldn't resolve default property of object originCoord(2). Click for more: 'ms-help://MS.VSCC.v90/dv_commoner/local/redirect.htm?keyword="6A50421D-15FE-4896-8A1B-2EC21E9037B2"'
    'UPGRADE_WARNING: Couldn't resolve default property of object ZAxisCoord(1). Click for more: 'ms-help://MS.VSCC.v90/dv_commoner/local/redirect.htm?keyword="6A50421D-15FE-4896-8A1B-2EC21E9037B2"'
    'UPGRADE_WARNING: Couldn't resolve default property of object originCoord(1). Click for more: 'ms-help://MS.VSCC.v90/dv_commoner/local/redirect.htm?keyword="6A50421D-15FE-4896-8A1B-2EC21E9037B2"'
    'UPGRADE_WARNING: Couldn't resolve default property of object ZAxisCoord(0). Click for more: 'ms-help://MS.VSCC.v90/dv_commoner/local/redirect.htm?keyword="6A50421D-15FE-4896-8A1B-2EC21E9037B2"'
    'UPGRADE_WARNING: Couldn't resolve default property of object originCoord(). Click for more: 'ms-help://MS.VSCC.v90/dv_commoner/local/redirect.htm?keyword="6A50421D-15FE-4896-8A1B-2EC21E9037B2"'
    theZDir = theHSF.AddNewDirectionByCoord(originCoord(0) - ZAxisCoord(0), originCoord(1) - ZAxisCoord(1), originCoord(2) - ZAxisCoord(2))

    ' Construct some extremums and check the coordinates against the mins/maxs
    Dim theExtremums(5) As Object
    'UPGRADE_WARNING: Couldn't resolve default property of object theXDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(0) = theHSF.AddNewExtremum(theObjectRef, theXDir, 1)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theYDir. Click for more: 'ms-help://MS.VSCC.v90/dv_commoner/local/redirect.htm?keyword="6A50421D-15FE-4896-8A1B-2EC21E9037B2"'
    theExtremums(0).Direction2 = theYDir
    'UPGRADE_WARNING: Couldn't resolve default property of object theExtremums().ExtremumType2. Click for more: 'ms-help://MS.VSCC.v90/dv_commoner/local/redirect.htm?keyword="6A50421D-15FE-4896-8A1B-2EC21E9037B2"'
    theExtremums(0).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theZDir. Click for more: 'ms-help://MS.VSCC.v90/dv_commoner/local/redirect.htm?keyword="6A50421D-15FE-4896-8A1B-2EC21E9037B2"'
    theExtremums(0).Direction3 = theZDir
    'UPGRADE_WARNING: Couldn't resolve default property of object theExtremums().ExtremumType3. Click for more: 'ms-help://MS.VSCC.v90/dv_commoner/local/redirect.htm?keyword="6A50421D-15FE-4896-8A1B-2EC21E9037B2"'
    theExtremums(0).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(0))
    ' On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(0))
    If Err.Number <> 0 Then
        mySelection.Clear()
        'UPGRADE_WARNING: Couldn't resolve default property of object tempBody. Click for more: 'ms-help://MS.VSCC.v90/dv_commoner/local/redirect.htm?keyword="6A50421D-15FE-4896-8A1B-2EC21E9037B2"'
        mySelection.Add(tempBody)
        'UPGRADE_WARNING: Couldn't resolve default property of object myHBShapeAssemble. Click for more: 'ms-help://MS.VSCC.v90/dv_commoner/local/redirect.htm?keyword="6A50421D-15FE-4896-8A1B-2EC21E9037B2"'
        If hCnt > 1 Then
            mySelection.Add(myHBShapeAssemble)
        End If
        mySelection.Delete()
        Exit Sub
    End If
    On Error GoTo 0

    'UPGRADE_WARNING: Couldn't resolve default property of object theXDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(1) = theHSF.AddNewExtremum(theObjectRef, theXDir, 0)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theYDir. Click for more: 'ms-help://MS.VSCC.v90/dv_commoner/local/redirect.htm?keyword="6A50421D-15FE-4896-8A1B-2EC21E9037B2"'
    theExtremums(1).Direction2 = theYDir
    'UPGRADE_WARNING: Couldn't resolve default property of object theExtremums().ExtremumType2. Click for more: 'ms-help://MS.VSCC.v90/dv_commoner/local/redirect.htm?keyword="6A50421D-15FE-4896-8A1B-2EC21E9037B2"'
    theExtremums(1).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theZDir. Click for more: 'ms-help://MS.VSCC.v90/dv_commoner/local/redirect.htm?keyword="6A50421D-15FE-4896-8A1B-2EC21E9037B2"'
    theExtremums(1).Direction3 = theZDir
    'UPGRADE_WARNING: Couldn't resolve default property of object theExtremums().ExtremumType3. Click for more: 'ms-help://MS.VSCC.v90/dv_commoner/local/redirect.htm?keyword="6A50421D-15FE-4896-8A1B-2EC21E9037B2"'
    theExtremums(1).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(1))
    On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(1))

    'UPGRADE_WARNING: Couldn't resolve default property of object theYDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(2) = theHSF.AddNewExtremum(theObjectRef, theYDir, 1)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theZDir. Click for more: 'ms-help://MS.VSCC.v90/dv_commoner/local/redirect.htm?keyword="6A50421D-15FE-4896-8A1B-2EC21E9037B2"'
    theExtremums(2).Direction2 = theZDir
    'UPGRADE_WARNING: Couldn't resolve default property of object theExtremums().ExtremumType2. Click for more: 'ms-help://MS.VSCC.v90/dv_commoner/local/redirect.htm?keyword="6A50421D-15FE-4896-8A1B-2EC21E9037B2"'
    theExtremums(2).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theXDir. Click for more: 'ms-help://MS.VSCC.v90/dv_commoner/local/redirect.htm?keyword="6A50421D-15FE-4896-8A1B-2EC21E9037B2"'
    theExtremums(2).Direction3 = theXDir
    'UPGRADE_WARNING: Couldn't resolve default property of object theExtremums().ExtremumType3. Click for more: 'ms-help://MS.VSCC.v90/dv_commoner/local/redirect.htm?keyword="6A50421D-15FE-4896-8A1B-2EC21E9037B2"'
    theExtremums(2).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(2))
    On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(2))
    On Error GoTo 0

    'UPGRADE_WARNING: Couldn't resolve default property of object theYDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(3) = theHSF.AddNewExtremum(theObjectRef, theYDir, 0)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theZDir. Click for more: 'ms-help://MS.VSCC.v90/dv_commoner/local/redirect.htm?keyword="6A50421D-15FE-4896-8A1B-2EC21E9037B2"'
    theExtremums(3).Direction2 = theZDir
    'UPGRADE_WARNING: Couldn't resolve default property of object theExtremums().ExtremumType2. Click for more: 'ms-help://MS.VSCC.v90/dv_commoner/local/redirect.htm?keyword="6A50421D-15FE-4896-8A1B-2EC21E9037B2"'
    theExtremums(3).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theXDir. Click for more: 'ms-help://MS.VSCC.v90/dv_commoner/local/redirect.htm?keyword="6A50421D-15FE-4896-8A1B-2EC21E9037B2"'
    theExtremums(3).Direction3 = theXDir
    'UPGRADE_WARNING: Couldn't resolve default property of object theExtremums().ExtremumType3. Click for more: 'ms-help://MS.VSCC.v90/dv_commoner/local/redirect.htm?keyword="6A50421D-15FE-4896-8A1B-2EC21E9037B2"'
    theExtremums(3).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(3))
    On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(3))
    On Error GoTo 0

    'UPGRADE_WARNING: Couldn't resolve default property of object theZDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(4) = theHSF.AddNewExtremum(theObjectRef, theZDir, 1)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theXDir. Click for more: 'ms-help://MS.VSCC.v90/dv_commoner/local/redirect.htm?keyword="6A50421D-15FE-4896-8A1B-2EC21E9037B2"'
    theExtremums(4).Direction2 = theXDir
    'UPGRADE_WARNING: Couldn't resolve default property of object theExtremums().ExtremumType2. Click for more: 'ms-help://MS.VSCC.v90/dv_commoner/local/redirect.htm?keyword="6A50421D-15FE-4896-8A1B-2EC21E9037B2"'
    theExtremums(4).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theYDir. Click for more: 'ms-help://MS.VSCC.v90/dv_commoner/local/redirect.htm?keyword="6A50421D-15FE-4896-8A1B-2EC21E9037B2"'
    theExtremums(4).Direction3 = theYDir
    'UPGRADE_WARNING: Couldn't resolve default property of object theExtremums().ExtremumType3. Click for more: 'ms-help://MS.VSCC.v90/dv_commoner/local/redirect.htm?keyword="6A50421D-15FE-4896-8A1B-2EC21E9037B2"'
    theExtremums(4).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(4))
    On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(4))
    On Error GoTo 0

    'UPGRADE_WARNING: Couldn't resolve default property of object theZDir. Click for more: 'ms-help://MS.VSCC.v90/dv_commoner/local/redirect.htm?keyword="6A50421D-15FE-4896-8A1B-2EC21E9037B2"'
    'UPGRADE_WARNING: Couldn't resolve default property of object theObjectRef. Click for more: 'ms-help://MS.VSCC.v90/dv_commoner/local/redirect.htm?keyword="6A50421D-15FE-4896-8A1B-2EC21E9037B2"'
    theExtremums(5) = theHSF.AddNewExtremum(theObjectRef, theZDir, 0)
    'UPGRADE_WARNING: Couldn't resolve default property of object theExtremums().Direction2. Click for more: 'ms-help://MS.VSCC.v90/dv_commoner/local/redirect.htm?keyword="6A50421D-15FE-4896-8A1B-2EC21E9037B2"'
    'UPGRADE_WARNING: Couldn't resolve default property of object theXDir. Click for more: 'ms-help://MS.VSCC.v90/dv_commoner/local/redirect.htm?keyword="6A50421D-15FE-4896-8A1B-2EC21E9037B2"'
    theExtremums(5).Direction2 = theXDir
    'UPGRADE_WARNING: Couldn't resolve default property of object theExtremums().ExtremumType2. Click for more: 'ms-help://MS.VSCC.v90/dv_commoner/local/redirect.htm?keyword="6A50421D-15FE-4896-8A1B-2EC21E9037B2"'
    theExtremums(5).ExtremumType2 = 1
    'UPGRADE_WARNING: Couldn't resolve default property of object theExtremums().Direction3. Click for more: 'ms-help://MS.VSCC.v90/dv_commoner/local/redirect.htm?keyword="6A50421D-15FE-4896-8A1B-2EC21E9037B2"'
    'UPGRADE_WARNING: Couldn't resolve default property of object theYDir. Click for more: 'ms-help://MS.VSCC.v90/dv_commoner/local/redirect.htm?keyword="6A50421D-15FE-4896-8A1B-2EC21E9037B2"'
    theExtremums(5).Direction3 = theYDir
    'UPGRADE_WARNING: Couldn't resolve default property of object theExtremums().ExtremumType3. Click for more: 'ms-help://MS.VSCC.v90/dv_commoner/local/redirect.htm?keyword="6A50421D-15FE-4896-8A1B-2EC21E9037B2"'
    theExtremums(5).ExtremumType3 = 1
    'UPGRADE_WARNING: Couldn't resolve default property of object tempBody.AppendHybridShape. Click for more: 'ms-help://MS.VSCC.v90/dv_commoner/local/redirect.htm?keyword="6A50421D-15FE-4896-8A1B-2EC21E9037B2"'
    tempBody.AppendHybridShape(theExtremums(5))
    On Error Resume Next
    'UPGRADE_WARNING: Couldn't resolve default property of object theExtremums(). Click for more: 'ms-help://MS.VSCC.v90/dv_commoner/local/redirect.htm?keyword="6A50421D-15FE-4896-8A1B-2EC21E9037B2"'
    myBodyPart.UpdateObject(theExtremums(5))
    On Error GoTo 0

    Dim aPoint As Object
    Dim theEXRef As Object
    Dim dCoords(2) As Object
    Dim dResult(2) As Object
    Dim ii, j As Short
    For ii = 0 To 5
        'UPGRADE_WARNING: Couldn't resolve default property of object theExtremums(). Click for more: 'ms-help://MS.VSCC.v90/dv_commoner/local/redirect.htm?keyword="6A50421D-15FE-4896-8A1B-2EC21E9037B2"'
        theEXRef = myBodyPart.CreateReferenceFromObject(theExtremums(ii))
        On Error Resume Next
        'UPGRADE_WARNING: Couldn't resolve default property of object theEXRef. Click for more: 'ms-help://MS.VSCC.v90/dv_commoner/local/redirect.htm?keyword="6A50421D-15FE-4896-8A1B-2EC21E9037B2"'
        aPoint = theHSF.AddNewPointDatum(theEXRef)
        'UPGRADE_WARNING: Couldn't resolve default property of object aPoint.Compute. Click for more: 'ms-help://MS.VSCC.v90/dv_commoner/local/redirect.htm?keyword="6A50421D-15FE-4896-8A1B-2EC21E9037B2"'
        aPoint.Compute()
        'UPGRADE_WARNING: Couldn't resolve default property of object aPoint.GetCoordinates. Click for more: 'ms-help://MS.VSCC.v90/dv_commoner/local/redirect.htm?keyword="6A50421D-15FE-4896-8A1B-2EC21E9037B2"'
        aPoint.GetCoordinates(dCoords)
        On Error GoTo 0

        For j = 0 To 2
            'UPGRADE_WARNING: Couldn't resolve default property of object mins(j). Click for more: 'ms-help://MS.VSCC.v90/dv_commoner/local/redirect.htm?keyword="6A50421D-15FE-4896-8A1B-2EC21E9037B2"'
            'UPGRADE_WARNING: Couldn't resolve default property of object dCoords(j). Click for more: 'ms-help://MS.VSCC.v90/dv_commoner/local/redirect.htm?keyword="6A50421D-15FE-4896-8A1B-2EC21E9037B2"'
            If dCoords(j) < mins(j) Then
                'UPGRADE_WARNING: Couldn't resolve default property of object dCoords(j). Click for more: 'ms-help://MS.VSCC.v90/dv_commoner/local/redirect.htm?keyword="6A50421D-15FE-4896-8A1B-2EC21E9037B2"'
                'UPGRADE_WARNING: Couldn't resolve default property of object mins(j). Click for more: 'ms-help://MS.VSCC.v90/dv_commoner/local/redirect.htm?keyword="6A50421D-15FE-4896-8A1B-2EC21E9037B2"'
                mins(j) = dCoords(j)
            End If
            'UPGRADE_WARNING: Couldn't resolve default property of object maxs(j). Click for more: 'ms-help://MS.VSCC.v90/dv_commoner/local/redirect.htm?keyword="6A50421D-15FE-4896-8A1B-2EC21E9037B2"'
            'UPGRADE_WARNING: Couldn't resolve default property of object dCoords(j). Click for more: 'ms-help://MS.VSCC.v90/dv_commoner/local/redirect.htm?keyword="6A50421D-15FE-4896-8A1B-2EC21E9037B2"'
            If dCoords(j) > maxs(j) Then
                'UPGRADE_WARNING: Couldn't resolve default property of object dCoords(j). Click for more: 'ms-help://MS.VSCC.v90/dv_commoner/local/redirect.htm?keyword="6A50421D-15FE-4896-8A1B-2EC21E9037B2"'
                'UPGRADE_WARNING: Couldn't resolve default property of object maxs(j). Click for more: 'ms-help://MS.VSCC.v90/dv_commoner/local/redirect.htm?keyword="6A50421D-15FE-4896-8A1B-2EC21E9037B2"'
                maxs(j) = dCoords(j)
            End If
            Next
            Next

            ' Find Distance in X, Y, and Z and Convert to Inches
            'UPGRADE_WARNING: Couldn't resolve default property of object mins(0). Click for more: 'ms-help://MS.VSCC.v90/dv_commoner/local/redirect.htm?keyword="6A50421D-15FE-4896-8A1B-2EC21E9037B2"'
            'UPGRADE_WARNING: Couldn't resolve default property of object maxs(). Click for more: 'ms-help://MS.VSCC.v90/dv_commoner/local/redirect.htm?keyword="6A50421D-15FE-4896-8A1B-2EC21E9037B2"'
            sXLength = FormatNumber(Int((((maxs(0) - mins(0)) / 25.4) + 0.125) / 0.125) * 0.125, 3)
            'UPGRADE_WARNING: Couldn't resolve default property of object mins(1). Click for more: 'ms-help://MS.VSCC.v90/dv_commoner/local/redirect.htm?keyword="6A50421D-15FE-4896-8A1B-2EC21E9037B2"'
            'UPGRADE_WARNING: Couldn't resolve default property of object maxs(). Click for more: 'ms-help://MS.VSCC.v90/dv_commoner/local/redirect.htm?keyword="6A50421D-15FE-4896-8A1B-2EC21E9037B2"'
            sYLength = FormatNumber(Int((((maxs(1) - mins(1)) / 25.4) + 0.125) / 0.125) * 0.125, 3)
            'UPGRADE_WARNING: Couldn't resolve default property of object mins(2). Click for more: 'ms-help://MS.VSCC.v90/dv_commoner/local/redirect.htm?keyword="6A50421D-15FE-4896-8A1B-2EC21E9037B2"'
            'UPGRADE_WARNING: Couldn't resolve default property of object maxs(). Click for more: 'ms-help://MS.VSCC.v90/dv_commoner/local/redirect.htm?keyword="6A50421D-15FE-4896-8A1B-2EC21E9037B2"'
            sZLength = FormatNumber(Int((((maxs(2) - mins(2)) / 25.4) + 0.125) / 0.125) * 0.125, 3)
            'UPGRADE_WARNING: Couldn't resolve default property of object mins(). Click for more: 'ms-help://MS.VSCC.v90/dv_commoner/local/redirect.htm?keyword="6A50421D-15FE-4896-8A1B-2EC21E9037B2"'
            'UPGRADE_WARNING: Couldn't resolve default property of object sXMin. Click for more: 'ms-help://MS.VSCC.v90/dv_commoner/local/redirect.htm?keyword="6A50421D-15FE-4896-8A1B-2EC21E9037B2"'
            sXMin = FormatNumber(System.Math.Abs(mins(0)) / 25.4, 3)
            'UPGRADE_WARNING: Couldn't resolve default property of object mins(). Click for more: 'ms-help://MS.VSCC.v90/dv_commoner/local/redirect.htm?keyword="6A50421D-15FE-4896-8A1B-2EC21E9037B2"'
            'UPGRADE_WARNING: Couldn't resolve default property of object sYMin. Click for more: 'ms-help://MS.VSCC.v90/dv_commoner/local/redirect.htm?keyword="6A50421D-15FE-4896-8A1B-2EC21E9037B2"'
            sYMin = FormatNumber(System.Math.Abs(mins(1)) / 25.4, 3)

            Dim myBodyName As String
            'UPGRADE_WARNING: Couldn't resolve default property of object theStock.Name. Click for more: 'ms-help://MS.VSCC.v90/dv_commoner/local/redirect.htm?keyword="6A50421D-15FE-4896-8A1B-2EC21E9037B2"'
            myBodyName = theStock.Name
            Dim myPartParams As Object 'As Parameters
            myPartParams = myBodyPart.Parameters
            Dim myVolume As KnowledgewareTypeLib.Dimension
            On Error Resume Next
            'UPGRADE_WARNING: Couldn't resolve default property of object myPartParams.CreateDimension. Click for more: 'ms-help://MS.VSCC.v90/dv_commoner/local/redirect.htm?keyword="6A50421D-15FE-4896-8A1B-2EC21E9037B2"'
            myVolume = myPartParams.CreateDimension("Volume", "VOLUME", 0)
            Dim myVolumeRel As KnowledgewareTypeLib.Relation
            Dim myRels As KnowledgewareTypeLib.Relations
            myRels = myBodyPart.Relations
            'UPGRADE_WARNING: Couldn't resolve default property of object myVolume. Click for more: 'ms-help://MS.VSCC.v90/dv_commoner/local/redirect.htm?keyword="6A50421D-15FE-4896-8A1B-2EC21E9037B2"'
            myVolumeRel = myRels.CreateFormula("VolumeFormula", "", myVolume, "smartVolume(`" & myBodyName & "`)")
            sVolume = Replace(CStr(myVolume.ValueAsString), "in3", "")
            If InStr(sVolume, "mm3") > 0 Then
                sVolume = VB.Left(sVolume, Len(sVolume) - 3)
                sVolume = CStr(CDbl(sVolume) / 16387)
            ElseIf InStr(sVolume, "m3") > 0 Then
                sVolume = VB.Left(sVolume, Len(sVolume) - 2)
                sVolume = CStr(CDbl(sVolume) / 16.387)
            End If
 Delete:
            mySelection.Clear()
            'UPGRADE_WARNING: Couldn't resolve default property of object tempBody. Click for more: 'ms-help://MS.VSCC.v90/dv_commoner/local/redirect.htm?keyword="6A50421D-15FE-4896-8A1B-2EC21E9037B2"'
            mySelection.Add(tempBody)
            'UPGRADE_WARNING: Couldn't resolve default property of object myHBShapeAssemble. Click for more: 'ms-help://MS.VSCC.v90/dv_commoner/local/redirect.htm?keyword="6A50421D-15FE-4896-8A1B-2EC21E9037B2"'
            If hCnt > 1 Then
                mySelection.Add(myHBShapeAssemble)
            End If
            mySelection.Delete()

End Sub

' Take a Snapshot of Part in smaller Catia Window
Sub Snapshot(ByRef sFileName As String, ByRef sX As String, ByRef sY As String, ByRef sZ As String, ByRef myMass As Double, ByRef myName As String, ByRef sPicture As String)
    Dim sLastPicture As Object
    Dim rando As Object
    'Shut off file alerts (to stop warnings about overwriting filenames)
    'UPGRADE_WARNING: Couldn't resolve default property of object CATIA.DisplayFileAlerts. Click for more: 'ms-help://MS.VSCC.v90/dv_commoner/local/redirect.htm?keyword="6A50421D-15FE-4896-8A1B-2EC21E9037B2"'
    CATIA.DisplayFileAlerts = False
    '=================Save JPG File=========================
    Dim myViewer As Object 'As Viewer
    Dim myWin As INFITF.SpecsAndGeomWindow
    Dim color(2) As Object
    Dim myHeight, myWidth As Integer
    'UPGRADE_WARNING: Couldn't resolve default property of object CATIA.ActiveWindow. Click for more: 'ms-help://MS.VSCC.v90/dv_commoner/local/redirect.htm?keyword="6A50421D-15FE-4896-8A1B-2EC21E9037B2"'
    myViewer = CATIA.ActiveWindow.ActiveViewer
    'UPGRADE_WARNING: Couldn't resolve default property of object CATIA.ActiveWindow. Click for more: 'ms-help://MS.VSCC.v90/dv_commoner/local/redirect.htm?keyword="6A50421D-15FE-4896-8A1B-2EC21E9037B2"'
    myWin = CATIA.ActiveWindow
    'UPGRADE_WARNING: Couldn't resolve default property of object myViewer.GetBackgroundColor. Click for more: 'ms-help://MS.VSCC.v90/dv_commoner/local/redirect.htm?keyword="6A50421D-15FE-4896-8A1B-2EC21E9037B2"'
    myViewer.GetBackgroundColor(color)
    'UPGRADE_WARNING: Couldn't resolve default property of object CATIA.StartCommand. Click for more: 'ms-help://MS.VSCC.v90/dv_commoner/local/redirect.htm?keyword="6A50421D-15FE-4896-8A1B-2EC21E9037B2"'
    CATIA.StartCommand("CompassDisplayOff")
    'UPGRADE_WARNING: Couldn't resolve default property of object CATIA.StartCommand. Click for more: 'ms-help://MS.VSCC.v90/dv_commoner/local/redirect.htm?keyword="6A50421D-15FE-4896-8A1B-2EC21E9037B2"'
    CATIA.StartCommand("* iso")
    'UPGRADE_WARNING: Couldn't resolve default property of object myViewer.Viewpoint3D. Click for more: 'ms-help://MS.VSCC.v90/dv_commoner/local/redirect.htm?keyword="6A50421D-15FE-4896-8A1B-2EC21E9037B2"'
    'UPGRADE_WARNING: Couldn't resolve default property of object CATIA.ActiveDocument. Click for more: 'ms-help://MS.VSCC.v90/dv_commoner/local/redirect.htm?keyword="6A50421D-15FE-4896-8A1B-2EC21E9037B2"'
    myViewer.Viewpoint3D = CATIA.ActiveDocument.Cameras.Item(1)

    'UPGRADE_WARNING: Couldn't resolve default property of object myViewer.Update. Click for more: 'ms-help://MS.VSCC.v90/dv_commoner/local/redirect.htm?keyword="6A50421D-15FE-4896-8A1B-2EC21E9037B2"'
    myViewer.Update()
    'UPGRADE_WARNING: Couldn't resolve default property of object myViewer.Reframe. Click for more: 'ms-help://MS.VSCC.v90/dv_commoner/local/redirect.htm?keyword="6A50421D-15FE-4896-8A1B-2EC21E9037B2"'
    myViewer.Reframe()
    'UPGRADE_WARNING: Couldn't resolve default property of object myViewer.ZoomIn. Click for more: 'ms-help://MS.VSCC.v90/dv_commoner/local/redirect.htm?keyword="6A50421D-15FE-4896-8A1B-2EC21E9037B2"'
    myViewer.ZoomIn()

    myHeight = myWin.Height
    myWidth = myWin.Width

    'UPGRADE_WARNING: Couldn't resolve default property of object CATIA.RefreshDisplay. Click for more: 'ms-help://MS.VSCC.v90/dv_commoner/local/redirect.htm?keyword="6A50421D-15FE-4896-8A1B-2EC21E9037B2"'
    CATIA.RefreshDisplay = True
    System.Windows.Forms.Application.DoEvents()
    On Error Resume Next
    myWin.Layout = INFITF.CatSpecsAndGeomWindowLayout.catWindowGeomOnly
    On Error GoTo 0

    myWin.Top = 30
    myWin.Left = 10
    myWin.Height = 600
    myWin.Width = 800
    'UPGRADE_WARNING: Couldn't resolve default property of object myViewer.Reframe. Click for more: 'ms-help://MS.VSCC.v90/dv_commoner/local/redirect.htm?keyword="6A50421D-15FE-4896-8A1B-2EC21E9037B2"'
    myViewer.Reframe()
    'UPGRADE_WARNING: Array has a new behavior. Click for more: 'ms-help://MS.VSCC.v90/dv_commoner/local/redirect.htm?keyword="9B7D5ADD-D8FE-4819-A36C-6DEDAF088CC7"'
    'UPGRADE_WARNING: Couldn't resolve default property of object myViewer.PutBackgroundColor. Click for more: 'ms-help://MS.VSCC.v90/dv_commoner/local/redirect.htm?keyword="6A50421D-15FE-4896-8A1B-2EC21E9037B2"'
    myViewer.PutBackgroundColor(Array(1, 1, 1))
    'UPGRADE_WARNING: Couldn't resolve default property of object CATIA.StartCommand. Click for more: 'ms-help://MS.VSCC.v90/dv_commoner/local/redirect.htm?keyword="6A50421D-15FE-4896-8A1B-2EC21E9037B2"'
    CATIA.StartCommand("Fit All In")
    'UPGRADE_WARNING: Couldn't resolve default property of object CATIA.StartCommand. Click for more: 'ms-help://MS.VSCC.v90/dv_commoner/local/redirect.htm?keyword="6A50421D-15FE-4896-8A1B-2EC21E9037B2"'
    CATIA.StartCommand("Zoom In")
    'UPGRADE_WARNING: Couldn't resolve default property of object myViewer.Update. Click for more: 'ms-help://MS.VSCC.v90/dv_commoner/local/redirect.htm?keyword="6A50421D-15FE-4896-8A1B-2EC21E9037B2"'
    myViewer.Update()
    System.Windows.Forms.Application.DoEvents()
    If chkAuto.CheckState = 0 Then
        MsgBox "The Part Weight is " & myMass & "lb" & vbCrLf & "The X Length is :  " & sX & vbCrLf & "The Y Length is :  " & sY & vbCrLf & "The Z Length is :  " & sZ & vbCrLf & vbCrLf & "Rotate Iso View for Snapshot", MsgBoxStyle.Information, "Part Size of " & myName
    End If
    Dim sPictureName, sPicturePath As String
    sPictureName = Mid(sFileName, InStrRev(sFileName, "\") + 1, 99)
    sPicturePath = Mid(sFileName, 1, InStrRev(sFileName, "\"))
    sPictureName = Replace(sPictureName, ",", "")
    sPictureName = Replace(sPictureName, "|", "_")



    intNumber = Int((500 - 1 + 1) * Rnd + 1)
    'UPGRADE_ISSUE: The preceding line couldn't be parsed. Click for more: 'ms-help://MS.VSCC.v90/dv_commoner/local/redirect.htm?keyword="82EBB1AE-1FCB-4FEF-9E6C-8736A316F8A7"'

    rando()
    String rando = intNumber
    'UPGRADE_ISSUE: The preceding line couldn't be parsed. Click for more: 'ms-help://MS.VSCC.v90/dv_commoner/local/redirect.htm?keyword="82EBB1AE-1FCB-4FEF-9E6C-8736A316F8A7"'

    If Len(sPictureName) > 22 Then
        'UPGRADE_WARNING: Couldn't resolve default property of object rando. Click for more: 'ms-help://MS.VSCC.v90/dv_commoner/local/redirect.htm?keyword="6A50421D-15FE-4896-8A1B-2EC21E9037B2"'
        sPicture = sPicturePath & Mid(sPictureName, 1, 22) & rando & ".bmp"
    Else
        'UPGRADE_WARNING: Couldn't resolve default property of object rando. Click for more: 'ms-help://MS.VSCC.v90/dv_commoner/local/redirect.htm?keyword="6A50421D-15FE-4896-8A1B-2EC21E9037B2"'
        sPicture = sFileName & rando & ".bmp"
    End If
    ' Check if File Exists
    Dim fso As Scripting.FileSystemObject
    Dim iLastNumb As Short
    fso = New Scripting.FileSystemObject
    Do
        If fso.FileExists(sPicture) Then
            iLastNumb = iLastNumb + 1
            If Len(sPictureName) > 22 Then
                'UPGRADE_WARNING: Couldn't resolve default property of object rando. Click for more: 'ms-help://MS.VSCC.v90/dv_commoner/local/redirect.htm?keyword="6A50421D-15FE-4896-8A1B-2EC21E9037B2"'
                sPicture = sPicturePath & Mid(sPictureName, 1, 19) & rando & "(" & iLastNumb & ").bmp"
            Else
                'UPGRADE_WARNING: Couldn't resolve default property of object rando. Click for more: 'ms-help://MS.VSCC.v90/dv_commoner/local/redirect.htm?keyword="6A50421D-15FE-4896-8A1B-2EC21E9037B2"'
                sPicture = sFileName & rando & "(" & iLastNumb & ").bmp"
            End If
        End If
    Loop Until fso.FileExists(sPicture) = False
    'UPGRADE_NOTE: Object fso may not be destroyed until it is garbage collected. Click for more: 'ms-help://MS.VSCC.v90/dv_commoner/local/redirect.htm?keyword="6E35BFF6-CD74-4B09-9689-3E1A43DF8969"'
    fso = Nothing

    'UPGRADE_WARNING: Couldn't resolve default property of object myViewer.CaptureToFile. Click for more: 'ms-help://MS.VSCC.v90/dv_commoner/local/redirect.htm?keyword="6A50421D-15FE-4896-8A1B-2EC21E9037B2"'
    myViewer.CaptureToFile NFITF.CatCaptureFormat.catCaptureFormatBMP, sPicture
    'UPGRADE_WARNING: Couldn't resolve default property of object sLastPicture. Click for more: 'ms-help://MS.VSCC.v90/dv_commoner/local/redirect.htm?keyword="6A50421D-15FE-4896-8A1B-2EC21E9037B2"'
    sLastPicture = sPicture

    'UPGRADE_WARNING: Couldn't resolve default property of object myViewer.Update. Click for more: 'ms-help://MS.VSCC.v90/dv_commoner/local/redirect.htm?keyword="6A50421D-15FE-4896-8A1B-2EC21E9037B2"'
    myViewer.Update()
    'UPGRADE_WARNING: Couldn't resolve default property of object myViewer.PutBackgroundColor. Click for more: 'ms-help://MS.VSCC.v90/dv_commoner/local/redirect.htm?keyword="6A50421D-15FE-4896-8A1B-2EC21E9037B2"'
    myViewer.PutBackgroundColor(color)
    myWin.Layout = INFITF.CatSpecsAndGeomWindowLayout.catWindowSpecsAndGeom
    myWin.Height = myHeight
    myWin.Width = myWidth
    myWin.Top = -1
    myWin.Left = -1
    '=======================================================
    'UPGRADE_WARNING: Couldn't resolve default property of object myViewer.Viewpoint3D. Click for more: 'ms-help://MS.VSCC.v90/dv_commoner/local/redirect.htm?keyword="6A50421D-15FE-4896-8A1B-2EC21E9037B2"'
    'UPGRADE_WARNING: Couldn't resolve default property of object CATIA.ActiveDocument. Click for more: 'ms-help://MS.VSCC.v90/dv_commoner/local/redirect.htm?keyword="6A50421D-15FE-4896-8A1B-2EC21E9037B2"'
    myViewer.Viewpoint3D = CATIA.ActiveDocument.Cameras.Item(1)
    'UPGRADE_WARNING: Couldn't resolve default property of object CATIA.ActiveWindow. Click for more: 'ms-help://MS.VSCC.v90/dv_commoner/local/redirect.htm?keyword="6A50421D-15FE-4896-8A1B-2EC21E9037B2"'
    CATIA.ActiveWindow.ActiveViewer.Reframe()
    System.Windows.Forms.Application.DoEvents()
End Sub

Sub HidePlanes(myPart, mySelection)
    ' Hide Planes
    Set    myOriginElements = myPart.OriginElements

    Set myHSPlaneExplicit = myOriginElements.PlaneXY
    mySelection.Add(myHSPlaneExplicit)
    Set myHSPlaneExplicit = myOriginElements.PlaneYZ
    mySelection.Add(myHSPlaneExplicit)
    Set myHSPlaneExplicit = myOriginElements.PlaneZX
    mySelection.Add(myHSPlaneExplicit)
    Set myVisPropertySet = mySelection.VisProperties
    'UPGRADE_WARNING: Couldn't resolve default property of object myVisPropertySet.SetShow. Click for more: 'ms-help://MS.VSCC.v90/dv_commoner/local/redirect.htm?keyword="6A50421D-15FE-4896-8A1B-2EC21E9037B2"'
    myVisPropertySet.SetShow(INFITF.CatVisPropertyShow.catVisPropertyNoShowAttr)
    Set myVisPropertySet = mySelection.VisProperties
    'UPGRADE_WARNING: Couldn't resolve default property of object myVisPropertySet.SetShow. Click for more: 'ms-help://MS.VSCC.v90/dv_commoner/local/redirect.htm?keyword="6A50421D-15FE-4896-8A1B-2EC21E9037B2"'
    myVisPropertySet.SetShow(INFITF.CatVisPropertyShow.catVisPropertyNoShowAttr)
End Sub

Sub ReFrameISO()
    Dim myViewer As INFITF.Viewer
    'UPGRADE_WARNING: Couldn't resolve default property of object CATIA.ActiveWindow. Click for more: 'ms-help://MS.VSCC.v90/dv_commoner/local/redirect.htm?keyword="6A50421D-15FE-4896-8A1B-2EC21E9037B2"'
    myViewer = CATIA.ActiveWindow.ActiveViewer
    'UPGRADE_WARNING: Couldn't resolve default property of object myViewer.Viewpoint3D. Click for more: 'ms-help://MS.VSCC.v90/dv_commoner/local/redirect.htm?keyword="6A50421D-15FE-4896-8A1B-2EC21E9037B2"'
    'UPGRADE_WARNING: Couldn't resolve default property of object CATIA.ActiveDocument. Click for more: 'ms-help://MS.VSCC.v90/dv_commoner/local/redirect.htm?keyword="6A50421D-15FE-4896-8A1B-2EC21E9037B2"'
    myViewer.Viewpoint3D = CATIA.ActiveDocument.Cameras.Item(1)
    myViewer.ZoomIn()
    myViewer.Reframe()
    'UPGRADE_WARNING: Couldn't resolve default property of object CATIA.StartCommand. Click for more: 'ms-help://MS.VSCC.v90/dv_commoner/local/redirect.htm?keyword="6A50421D-15FE-4896-8A1B-2EC21E9037B2"'
    CATIA.StartCommand("Fit All In")
    'UPGRADE_WARNING: Couldn't resolve default property of object CATIA.StartCommand. Click for more: 'ms-help://MS.VSCC.v90/dv_commoner/local/redirect.htm?keyword="6A50421D-15FE-4896-8A1B-2EC21E9037B2"'
    CATIA.StartCommand("* iso")

End Sub

Sub AddHybridBodies(myPart, mySelection)
    j9 = 0
    Do
        j9 = j9 + 1
        mySelection.Add(myPart.HybridBodies.Item(j9))
    Loop While j9 <=myPart.HybridBodies.Count
End Sub

Sub AddBodies(myPart, mySelection)
    j9 = 0
    Do
        j9 = j9 + 1
        mySelection.Add(myPart.Bodies.Item(j9))
    Loop While j9 <=myPart.Bodies.Count
End Sub

Sub HideAnnotations(myPart, mySelection)
    If myPart.AnnotationSets.Count > 0 Then
        mySelection.Clear()
        'UPGRADE_WARNING: Couldn't resolve default property of object myPart.AnnotationSets.Item. Click for more: 'ms-help://MS.VSCC.v90/dv_commoner/local/redirect.htm?keyword="6A50421D-15FE-4896-8A1B-2EC21E9037B2"'
        mySelection.Add(myPart.AnnotationSets.Item(1))
        myVisPropertySet = mySelection.VisProperties
        'UPGRADE_WARNING: Couldn't resolve default property of object myVisPropertySet.SetShow. Click for more: 'ms-help://MS.VSCC.v90/dv_commoner/local/redirect.htm?keyword="6A50421D-15FE-4896-8A1B-2EC21E9037B2"'
        myVisPropertySet.SetShow(INFITF.CatVisPropertyShow.catVisPropertyNoShowAttr)
        mySelection.Clear()
    End If

End Sub

Sub AddHybridShapes(myPart, mySelection)
    Do
        j5 = j5 + 1
        Set hybridBodies = myPart.HybridBodies As HybridBodies
        Set myHBBody = hybridBodies.Item(j5) As HybridBody
        Set hybridShapes = myHBBody.HybridShapes As HybridShapes

        If hybridShapes.Count > 0 Then
            x = 0
            Do

                x = x + 1
                myHBShape = myHBBody.HybridShapes.Item(x)
                If TypeName(myHBShape) = "HybridShapeSurfaceExplicit" Then
                    nBodys = nBodys + 1
                    If iType = 1 Then
                        mySelection.Add(myHBBody)
                    End If
                    x = myHBBody.HybridShapes.Count + 1
                End If

            Loop While x <= myHBBody.HybridShapes.Count
        End If

    Loop While j5 < myPart.HybridBodies.Count
End Sub




Sub CATMain()



    ' MsgBox "It ran"
    CATIA.StatusBar = "Executed"
    Dim I As Object
    Dim fs As Object
    Dim sPicture As Object
    Dim myBodyPart As Object
    Dim sAnswer As Object
    Dim mySel As Object
    Dim iRet As Object
    Dim myWorksheet As Object

    Dim dirPath As String
    dirList = "C:\Catia\Project_Estimating"

    ' Select the Step File Directory
    Dim myPath As String
    myPath = dirList

    If myPath = "" Then
        Exit Sub
    End If

    ' Loop thur the Catia, Step, and IGES Files
    Dim sFileName, sPath As String
    Dim strDirSearch As String
    Dim sDirName As String
    sDirName = Mid(myPath, InStrRev(myPath, "\") + 1)

    ' Define Dir to Save files from Catia
    Dim mySaveDir As String
    mySaveDir = "TSG - Translated Data"
    Dim myCopiedData As String
    myCopiedData = "Supplied CAD"

    ' Excel
    Dim myExcel As Microsoft.Office.Interop.Excel.Application
    'UPGRADE_WARNING: Lower bound of array myPartNames was changed from 1 to 0. Click for more: 'ms-help://MS.VSCC.v90/dv_commoner/local/redirect.htm?keyword="0F1C9BE1-AF9D-476E-83B1-17D43BECFF20"'
    Dim myPartNames(888) As String
    'UPGRADE_WARNING: Lower bound of array myFileNames was changed from 1 to 0. Click for more: 'ms-help://MS.VSCC.v90/dv_commoner/local/redirect.htm?keyword="0F1C9BE1-AF9D-476E-83B1-17D43BECFF20"'
    Dim myFileNames(888) As String
    Dim iCnt As Short ' R24 Part Count
    'UPGRADE_WARNING: Lower bound of array sR24PartNames was changed from 1 to 0. Click for more: 'ms-help://MS.VSCC.v90/dv_commoner/local/redirect.htm?keyword="0F1C9BE1-AF9D-476E-83B1-17D43BECFF20"'
    Dim sR24PartNames(99) As String
    Dim iPartCnt As Short ' Count of PartNames
    Dim myMass As Double
    Dim myPartNumber As String
    Dim j As Short
    Dim nBodys As Short ' Number of Bodies to process
    Dim iBody As Short ' Current body to process
    Dim iRow As Short
    ' Open Excel Output file Template
    Set myExcel = CreateObject("Excel.Application")
    myExcel.Workbooks.Open("C:\Catia\Project_Estimating\CAD Info.xlsx")
    Dim myWorkbook As Microsoft.Office.Interop.Excel.Workbook
    Set myWorkbook = myExcel.Workbooks.Item(1)
    myWorkbook.Activate()
    'UPGRADE_WARNING: Couldn't resolve default property of object myWorkbook.Sheets().Select. Click for more: 'ms-help://MS.VSCC.v90/dv_commoner/local/redirect.htm?keyword="6A50421D-15FE-4896-8A1B-2EC21E9037B2"'
    myWorkbook.Sheets(1).Select()
    ' Open the Excel Template and Update
    Set myWorksheet = myWorkbook.ActiveSheet
    'UPGRADE_WARNING: Couldn't resolve default property of object myWorksheet.Columns. Click for more: 'ms-help://MS.VSCC.v90/dv_commoner/local/redirect.htm?keyword="6A50421D-15FE-4896-8A1B-2EC21E9037B2"'
    myWorksheet.Columns("B:B").ColumnWidth = 20
    ' Uncomment this line to make Excel visible.
    'myExcel.Visible = True
    iRow = 2

    Dim iType As Short
    Dim fsys As Scripting.FileSystemObject
    Dim myProductDoc As Object
    Dim myPartDocument As Object
    Dim myPart As MECMOD.Part
    Dim myBody As MECMOD.Body
    Dim myVisPropertySet As Object
    Dim myVersion As String
    Dim thisRev As Integer
    Dim myProd As ProductStructureTypeLib.Product
    Dim myShapes As MECMOD.Shapes
    Dim myHBBody As MECMOD.HybridBody
    Dim myHBShape As MECMOD.HybridShape
    Dim x As Short
    Dim selfilter(1) As Object
    Dim hCnt As Short
    Dim myOriginElements As MECMOD.OriginElements
    Dim myHSPlaneExplicit As INFITF.AnyObject
    Dim sZ, sX, sY, sVolume As String
    Dim sPhotoFile As String
    Dim myThickness, sMatl, sPartName As String
    Dim oPicture As Object
    Dim myDoc As INFITF.Document
    Dim myProductDoc1 As ProductStructureTypeLib.ProductDocument
    Dim myPartDoc1 As MECMOD.PartDocument
    Dim jj As Short
    'UPGRADE_WARNING: Lower bound of array myObjects was changed from 1 to 0. Click for more: 'ms-help://MS.VSCC.v90/dv_commoner/local/redirect.htm?keyword="0F1C9BE1-AF9D-476E-83B1-17D43BECFF20"'
    Dim myObjects(100) As Object 'As VisPropertySet

    Set fsys = CreateObject("Scripting.FileSystemObject")
    Dim explicit_files(1) As String


    iType = 0
    ' For iType = 1 To 3
    ' Do
    iType = iType + 1
    If boolStep = False And iType = 2 Then
        iType = 3 ' Skip Step if no License
    End If
    If iType = 1 Then
        strDirSearch = myPath & "\" & "*.CATPart"
        ' Create SnapShot Dir
        ' On Error Resume Next
        ' If Not fsys.FolderExists()
        ' MsgBox myPath
        ' MsgBox mySaveDir
        If Not fsys.FolderExists(myPath & "\" & mySaveDir) Then
            fsys.CreateFolder(myPath & "\" & mySaveDir)
        End If
        If Not fsys.FolderExists(myPath & "\" & myCopiedData) Then
            fsys.CreateFolder(myPath & "\" & myCopiedData)
        End If
        If Not fsys.FolderExists(myPath & "\Photos") Then
            fsys.CreateFolder(myPath & "\Photos")
        End If

        If Not fsys.FolderExists(myPath & "\temp") Then
            fsys.CreateFolder(myPath & "\temp")
        End If
    End If

    found_file = False

    Set mainFolder = CreateObject("Scripting.FileSystemObject").GetFolder( "C:\Catia\Project_Estimating") As Folder



    explicit_files(0) = "C:\Catia\Project_Estimating\anz18577.geo_fin001.001999  refset PART.CATPart"
    explicit_files(1) = "C:\Catia\Project_Estimating\anz18578.geo_fin001.002999  refset PART.CATPart"


    j = -1
    Do

        j = j + 1

        sFileName = explicit_files(j)

        CATIA.StatusBar = "Opening " & sFileName
        ' On Error Resume Next
        ' MsgBox myPath & "\" & sFileName
        Set myPartDocument = CATIA.Documents.Open(sFileName) As PartDocument
        If Err.Number <> 0 Then
            MsgBox "Error Opening " & sFileName & vbCrLf & "Error is " & Err.Number & " " & Err.Description, MsgBoxStyle.Critical, "File Open Error"
        End If
        On Error GoTo 0
        ' Wait4()
        CATIA.RefreshDisplay = True
        Set myProductDoc = CATIA.ActiveDocument
        Set myProd = myProductDoc.Product
        CATIA.StatusBar = "Processing..."
        If myProd.Products.Count = 0 And InStr(1, myProductDoc.Name, "CATPart") > 0 Then
            Set myPart = myProductDoc.Part
            myPart.Update()

            Set mySelection = CATIA.ActiveDocument.Selection
            mySelection.Clear()

            nBodys = 0
            mySelection.Clear()

            AddHybridShapes myPart, mySelection
            AddBodies myPart, mySelection

            ' On Error Resume Next
            If nBodys > 1 Then
                If iType = 1 Then
                    Set myVisPropertySet = mySelection.VisProperties
                    myVisPropertySet.SetShow(INFITF.CatVisPropertyShow.catVisPropertyShowAttr)
                End If
                If True Then
                    nBodys = 1
                ElseIf iRet = MsgBoxResult.No Then
                    mySelection.Clear()
                    selfilter(0) = "Body"
                    selfilter(1) = "HybridBody"
                    MsgBox "Select the Part Bodys or GeoSets, then select the green ball to end the selection." & vbCrLf & "Or UNDO to Cancel", MsgBoxStyle.Information, "Part Bodys/GeoSets Selection"
                    mySel = mySelection
                    sAnswer = mySel.SelectElement3(selfilter, "Select the Part Bodys or GeoSets, then select the green ball to end the selection.", False, INFITF.CATMultiSelectionMode.CATMultiSelTriggWhenUserValidatesSelection, False)

                    If sAnswer = "Undo" Or sAnswer = "Cancel" Then
                        Exit Sub
                    End If
                    'UPGRADE_WARNING: Couldn't resolve default property of object mySel.Count. Click for more: 'ms-help://MS.VSCC.v90/dv_commoner/local/redirect.htm?keyword="6A50421D-15FE-4896-8A1B-2EC21E9037B2"'
                    nBodys = mySel.Count


                    hCnt = 0

                    Do
                        hCnt = hCnt + 1

                        myObjects(hCnt) = mySel.Item(hCnt).Value
                        'UPGRADE_WARNING: Couldn't resolve default property of object myObjects().Parent. Click for more: 'ms-help://MS.VSCC.v90/dv_commoner/local/redirect.htm?keyword="6A50421D-15FE-4896-8A1B-2EC21E9037B2"'
                        myBodyPart = myObjects(hCnt).Parent.Parent
                        'UPGRADE_WARNING: Couldn't resolve default property of object myBodyPart.Name. Click for more: 'ms-help://MS.VSCC.v90/dv_commoner/local/redirect.htm?keyword="6A50421D-15FE-4896-8A1B-2EC21E9037B2"'
                        'UPGRADE_WARNING: TypeName has a new behavior. Click for more: 'ms-help://MS.VSCC.v90/dv_commoner/local/redirect.htm?keyword="9B7D5ADD-D8FE-4819-A36C-6DEDAF088CC7"'


                    Loop While hCnt <= nBodys
                Else




                    AddBodies myPart, mySelection
                    AddHybridBodies myPart, mySelection


                End If
            Else
                nBodys = 1
                If myPart.MainBody.Shapes.Count = 0 Then
                    myObjects(1) = myPart.HybridBodies.Item(1)
                Else
                    myObjects(1) = myPart.MainBody
                End If
            End If


            HidePlanes myPart, mySelection
            mySelection.Clear()
        Else
            myPart = Nothing
            nBodys = 1
        End If

        iBody = 0
        Do
            iBody = iBody + 1

            If myProd.Products.Count > 0 Then ' Product
                myPartNumber = myProd.Name
            ElseIf iBody = 1 Then
                If iType = 3 Then
                    myPartNumber = VB.Left(sFileName, Len(sFileName) - 4)
                Else
                    myPartNumber = myPart.Name
                End If
            Else
                myPartNumber = myPart.Name & "-Part-" & iBody
            End If

            If myPart Is Nothing Then ' Product
                j = j
            Else
                mySelection.Clear()
                AddBodies myPart, mySelection
                AddHybridBodies myPart, mySelection

                Set myVisPropertySet = mySelection.VisProperties
                myVisPropertySet.SetShow(INFITF.CatVisPropertyShow.catVisPropertyNoShowAttr)
                mySelection.Clear()

                Set obj11 = myObjects(iBody) As Object

                MsgBox TypeName(obj)

                mySelection.Add(myObjects(iBody))
                myVisPropertySet.SetShow(INFITF.CatVisPropertyShow.catVisPropertyShowAttr)
                mySelection.Clear()
            End If
            ' Reframe View to ISO
            ' ReFrameISO()

            ' Find X, Y, Z
            sVolume = "0"
            'UPGRADE_WARNING: Couldn't resolve default property of object CATIA.StatusBar. Click for more: 'ms-help://MS.VSCC.v90/dv_commoner/local/redirect.htm?keyword="6A50421D-15FE-4896-8A1B-2EC21E9037B2"'
            CATIA.StatusBar = "Finding Size and Weight..."
            FindBoundingBoxXYZ myPart, myObjects(iBody), sX, sY, sZ, sVolume

            'Retrieve the mass just to show it worked
            myMass = System.Math.Round(CDbl(sVolume) * 0.284, 2)

            Wait4()
            System.Windows.Forms.Application.DoEvents()
            If myPart Is Nothing Then
                ' GoTo Duplicate
                Exit Sub
            End If
            ' Hide Annotation Sets

            HideAnnotations myPart, mySelection


            ' Take Snapshot
            'UPGRADE_WARNING: Couldn't resolve default property of object CATIA.StatusBar. Click for more: 'ms-help://MS.VSCC.v90/dv_commoner/local/redirect.htm?keyword="6A50421D-15FE-4896-8A1B-2EC21E9037B2"'
            CATIA.StatusBar = "Taking Snapshot..."
            Snapshot myPath & "\Photos\" & myPartNumber, sX, sY, sZ, myMass, (myProd.Name), sPhotoFile
            System.Windows.Forms.Application.DoEvents()

            ' 3DXML save
            If sVolume <> "0" Then
                'UPGRADE_WARNING: Couldn't resolve default property of object sPicture. Click for more: 'ms-help://MS.VSCC.v90/dv_commoner/local/redirect.htm?keyword="6A50421D-15FE-4896-8A1B-2EC21E9037B2"'
                sPicture = sFileName & ".3dxml"
                'UPGRADE_WARNING: Couldn't resolve default property of object sPicture. Click for more: 'ms-help://MS.VSCC.v90/dv_commoner/local/redirect.htm?keyword="6A50421D-15FE-4896-8A1B-2EC21E9037B2"'
                'UPGRADE_WARNING: Couldn't resolve default property of object myProductDoc.ExportData. Click for more: 'ms-help://MS.VSCC.v90/dv_commoner/local/redirect.htm?keyword="6A50421D-15FE-4896-8A1B-2EC21E9037B2"'
                myProductDoc.ExportData myPath & "\Photos\" & sPicture, "3dxml"
            End If

            CATIA.StatusBar = "Reading Parameters..."
            GetParams myPart, myProd, sMatl, myThickness, sPartName
            Wait4()
            myWorksheet.Cells(iRow, 1).Value = iRow - 1
            myWorksheet.Cells(iRow, 3).Value = sFileName
            myWorksheet.Cells(iRow, 4).Value = myPartNumber
            myWorksheet.Cells(iRow, 5).Value = sPartName
            If sX <> "0" Then
                myWorksheet.Cells(iRow, 6).Value = sX ' X Dimension
            End If

            If sY <> "0" Then
                myWorksheet.Cells(iRow, 7).Value = sY ' Y Dimension
            End If

            If sZ <> "0" Then
                myWorksheet.Cells(iRow, 8).Value = sZ ' Z Dimension
            End If
            myWorksheet.Cells(iRow, 9).Value = sMatl ' Matl
            myWorksheet.Cells(iRow, 10).Value = myThickness ' Material Thickness
            If myMass <> CDbl("0") Then
                myWorksheet.Cells(iRow, 11).Value = myMass ' Finished Weight
            End If
            myWorksheet.Cells(iRow, 18).Value = Mid(sPhotoFile, InStrRev(sPhotoFile, "\") + 1, 99)
            myWorksheet.Cells(iRow, 2).RowHeight = 80
            myWorksheet.Cells(iRow, 2).Select()
            oPicture = myExcel.ActiveSheet.Shapes.AddPicture(sPhotoFile, False, True, 1, 1, 100, 75)
            MsgBox = sPhotoFile
            With oPicture
                .Left = myExcel.ActiveSheet.Cells(iRow, 2).Left
                .Top = myExcel.ActiveSheet.Cells(iRow, 2).Top
                .Placement = 1
            End With
            iRow = iRow + 1

        Loop While iBody < nBodys



    Loop While kkk < 2

    myDoc = CATIA.ActiveDocument
    CATIA.DisplayFileAlerts = False
    fs = CreateObject("Scripting.FileSystemObject")
    fs.MoveFile myPath & "\" & sFileName, myPath & "\" & myCopiedData & "\" & sFileName
    fs = Nothing
    If iType = 1 Then
        If boolStep = True Then
            ' On Error Resume Next
            If InStr(1, myPart.Name, "|", 1) > 0 Or InStr(1, myPart.Name, ",", 1) > 0 Then
                sPartName = Replace(myPart.Name, "|", "_")
                sPartName = Replace(sPartName, ",", "_")
                myDoc.ExportData myPath & "\" & mySaveDir & "\" & sPartName & ".stp", "stp"
                myDoc.ExportData myPath & "\" & mySaveDir & "\" & sPartName & ".igs", "igs"
            Else
                myDoc.ExportData myPath & "\" & mySaveDir & "\" & myPart.Name & ".stp", "stp"
                myDoc.ExportData myPath & "\" & mySaveDir & "\" & myPart.Name & ".igs", "igs"
            End If
            On Error GoTo 0
        End If
        myDoc.Close()
    Else
        If iType = 2 Then
            myDoc.ExportData myPath & "\" & mySaveDir & "\" & VB.Left(sFileName, Len(sFileName) - 4) & ".igs", "igs"
        End If
        If iType = 3 And boolStep = True Then
            myDoc.ExportData myPath & "\" & mySaveDir & "\" & VB.Left(sFileName, Len(sFileName) - 4) & ".stp", "stp"
            myDoc.SaveAs myPath & "\" & mySaveDir & "\" & VB.Left(sFileName, Len(sFileName) - 4) & ".CATPart"
        Else
            myProductDoc1 = Nothing
            myPartDoc1 = Nothing
            myPart.Update()
            jj = 0
            Do
                jj = jj + 1


                If InStr(1, CATIA.Documents.Item(jj).Name, ".CATProduct") > 0 Then
                    myProductDoc1 = CATIA.Documents.Item(jj)
                    myProductDoc1.SaveAs myPath & "\" & mySaveDir & "\" & CATIA.Documents.Item(jj).Name
                ElseIf InStr(1, CATIA.Documents.Item(jj).Name, ".CATPart") > 0 And InStr(1, CATIA.Documents.Item(jj).Name, ".CATPart.CATPart") <= 0 Then
                    myPartDoc1 = CATIA.Documents.Item(jj)
                    myPartDoc1.SaveAsmy Path & "\" & mySaveDir & "\" & CATIA.Documents.Item(jj).Name
                End If
                ' Next
            Loop While jj <= CATIA.Documents.Count
            ' On Error Resume Next
            If Not myPartDoc1 Is Nothing Then
                myDoc.SaveAs(myPath & "\" & mySaveDir & "\" & myPart.Name & ".CATPart")
            End If
            If Not myProductDoc1 Is Nothing Then
                myProductDoc1.Close()
            End If
            If Not myPartDoc1 Is Nothing Then
                myPartDoc1.Close()
            End If
            On Error GoTo 0
        End If
        ' On Error Resume Next
        myPartDocument.Close()
        On Error GoTo 0
    End If
End Sub


' 1520
