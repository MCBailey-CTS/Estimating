Language="VBSCRIPT"

Dim mainDirectory as String


Dim fileName as String
Dim dotIndex As Integer
Dim fileLeaf As String
Dim dataExtension As String

Dim catDest As String
Dim stpDest As String
Dim igsDest As String
Dim igsPath As String
Dim stpPath As String
Dim photosPath As String
Dim translateIgsPath As Stringx
Dim translateStpPath As String
Dim translateCatPath As String

Dim catPath as String
Dim myExcel As Microsoft.Office.Interop.Excel.Application

Dim translateDirectory As String
Dim suppliedDirectory As String
Dim photosDirectory As String
Dim iRow As Integer
Dim objFSO As Object
Dim oFolder As Object



Function DisplayPart() As Part
    Select Case TypeName(CATIA.ActiveDocument)
     Case "PartDocument"
        Set DisplayPart = CATIA.ActiveDocument.Part

    End Select


End Function

Function DisplayDocument() As Document
    Set DisplayDocument= CATIA.ActiveDocument
End Function


Sub CATMain()

    ' MsgBox TypeName(DisplayPart())

    ' Return

    CATIA.DisplayFileAlerts = False

    ' Dim mainDirectory as String
    mainDirectory = "C:\Estimating\Project_Estimating"

    Set objFSO = Createobject("Scripting.FileSystemObject")



    translateDirectory = mainDirectory & "\TSG - Translated Data"

    suppliedDirectory = mainDirectory & "\Supplied Cad Data"

    photosDirectory = mainDirectory & "\Photos"



    objFSO.CreateFolder(translateDirectory)
    objFSO.CreateFolder(suppliedDirectory)
    objFSO.CreateFolder(photosDirectory)
    objFSO.CopyFile "C:\Catia\Project_Estimating\CAD Info.xlsx", mainDirectory & "\CAD Info.xlsx"





    Set myExcel = CreateObject("Excel.Application")

    myExcel.Workbooks.Open(mainDirectory & "\CAD Info.xlsx")

    Set myWorksheet = myExcel.Workbooks.Item(1).ActiveSheet

    myExcel.Workbooks.Item(1).ActiveSheet.Columns("B:B").ColumnWidth = 20


    iRow = 2

    Set oFolder = objFSO.GetFolder(mainDirectory)


    Process()
    Process()

    myExcel.Workbooks.Item(1).Save()
    myExcel.Quit()
    myExcel.Quit()


End Sub

Sub Process()


    Dim aPoint As Object
    Dim theEXRef As Object

    Dim dResult(2) As Object
    Dim ii, j As Short
    Dim theExtremums(5)
    Dim body As body
    ' Dim theHSF As HybridShapeTypeLib.HybridShapeFactory
    Dim theObjectRef As Object



    ' Dim dataPath As String

    ' Dim originCoord(2) As Object
    ' Dim XAxisCoord(2) As Object
    XAxisCoord = Array(1,0,0)
    YAxisCoord = Array(0,1,0)
    ZAxisCoord = Array(0,0,1)


    Dim selectedObject As Object

    ' Initialize the mins,maxs to impossible values
    mins = Array( 100000, 100000, 100000)
    maxs = Array( -100000, -100000, -100000)

    ' Evalute the Axis System Directions
    originCoord = Array(0,0,0)
    Dim Filter(1)
    Filter(0) = "Body"
    Filter(1) = "HybridBody"

    ' Filter = Array("Body","HybridBody")

    For Each oFile in oFolder.Files

        dataPath = oFile As String

        fileName = LCase(oFile.Name)

        dotIndex = InStrRev(fileName,".")

        fileLeaf = LCase(Left(fileName,dotIndex - 1))

        dataExtension = LCase(Mid(fileName, dotIndex))

        If dataExtension = ".iges" Then
            dataExtension = ".igs"

            dataPath = mainDirectory & "\" & fileLeaf & ".igs"

            objFSO.MoveFile oFile, dataPath
        End If



        catPath = mainDirectory & "\" & fileLeaf & ".catpart"

        igsPath = mainDirectory & "\" & fileLeaf & ".igs"

        stpPath = mainDirectory & "\" & fileLeaf & ".stp"

        photosPath = photosDirectory & "\" & fileLeaf & ".bmp"

        suppliedDataPath = suppliedDirectory & "\" & fileLeaf & dataExtension

        translateIgsPath = translateDirectory & "\" & fileLeaf & ".igs"

        translateStpPath = translateDirectory & "\" & fileLeaf & ".stp"

        translateCatPath = translateDirectory & "\" & fileLeaf & ".catpart"

        If dataExtension = ".catpart" Or dataExtension = ".igs" Or dataExtension = ".stp" Or dataExtension = ".step"  Then

            CATIA.Documents.Open(dataPath)

            CATIA.ActiveWindow.ActiveViewer.Reframe

        End If

        If dataExtension = ".stp" Or dataExtension = ".step" Then

            DisplayDocument().SaveAs mainDirectory & "\" & fileLeaf & ".CATPart"

            DisplayDocument().ExportData mainDirectory & "\" & fileLeaf & ".igs", "igs"

            stpDest = suppliedDataPath

            catDest = translateCatPath

            igsDest = translateIgsPath

        End If

        If dataExtension = ".igs" Then

            DisplayDocument().SaveAs mainDirectory & "\" & fileLeaf & ".CATPart"

            DisplayDocument().ExportData mainDirectory & "\" & fileLeaf & ".stp", "stp"

            stpDest = translateStpPath

            catDest = translateCatPath

            igsDest = suppliedDataPath

        End If

        If dataExtension = ".catpart" Then

            DisplayDocument().ExportData mainDirectory & "\" & fileLeaf & ".igs" , "igs"

            DisplayDocument().ExportData mainDirectory & "\" & fileLeaf & ".stp", "stp"

            stpDest = translateStpPath

            catDest = suppliedDataPath

            igsDest = translateIgsPath

        End If

        If dataExtension = ".catpart" Or dataExtension = ".igs" Or dataExtension = ".stp" Or dataExtension = ".step" Then

            Dim oSel as Selection
            Set oSel = DisplayDocument().selection

            oSel.Clear()


            F_Body = oSel.selectelement2(Filter, " Select Body in which you want to add", False)

            If F_Body = "Normal" Then

                CATIA.ActiveWindow.ActiveViewer.CaptureToFile catCaptureFormatBMP, photosPath

                Dim part As Part
                Set part = CATIA.ActiveDocument

                Dim myBodyPart As Part

                If TypeName(CATIA.ActiveDocument) = "PartDocument" Then
                    Set part = CATIA.ActiveDocument.Part
                Else
                    Set part = CATIA.ActiveDocument
                End If

                Set myBodyPart = part

                Set body = oSel.Item(1).Value

                Set theHSF = myBodyPart.HybridShapeFactory As HybridShapeTypeLib.HybridShapeFactory

                If TypeName(body) = "HybridBody" Then
                    Set selectedObject = body.HybridShapes.Item(1)
                Else
                    set selectedObject = body
                End If

                Set theObjectRef = myBodyPart.CreateReferenceFromObject(selectedObject)




                ' Make directions for X Y and Z

                Set theXDir = theHSF.AddNewDirectionByCoord(originCoord(0) - XAxisCoord(0), originCoord(1) - XAxisCoord(1), originCoord(2) - XAxisCoord(2))

                Set theYDir = theHSF.AddNewDirectionByCoord(originCoord(0) - YAxisCoord(0), originCoord(1) - YAxisCoord(1), originCoord(2) - YAxisCoord(2))

                Set theZDir = theHSF.AddNewDirectionByCoord(originCoord(0) - ZAxisCoord(0), originCoord(1) - ZAxisCoord(1), originCoord(2) - ZAxisCoord(2))

                SetExtremes myBodyPart, theExtremums, theHSF, theObjectRef, theXDir, theYDir, theZDir, 0, 1
                SetExtremes myBodyPart, theExtremums, theHSF, theObjectRef, theXDir, theYDir, theZDir, 1, 0
                SetExtremes myBodyPart, theExtremums, theHSF, theObjectRef, theYDir, theZDir, theXDir, 2, 1
                SetExtremes myBodyPart, theExtremums, theHSF, theObjectRef, theXDir, theYDir, theZDir, 3, 0
                SetExtremes myBodyPart, theExtremums, theHSF, theObjectRef, theZDir, theXDir, theYDir, 4, 1
                SetExtremes myBodyPart, theExtremums, theHSF, theObjectRef, theZDir, theXDir, theYDir, 5, 0

                FindExtremes myBodyPart, theHSF, theExtremums, mins, maxs

                ' Find Distance in X, Y, and Z and Convert to Inches
                sXLength = FormatNumber(Int((((maxs(0) - mins(0)) / 25.4) + 0.125) / 0.125) * 0.125, 3)
                sYLength = FormatNumber(Int((((maxs(1) - mins(1)) / 25.4) + 0.125) / 0.125) * 0.125, 3)
                sZLength = FormatNumber(Int((((maxs(2) - mins(2)) / 25.4) + 0.125) / 0.125) * 0.125, 3)

                FillOut  fileName, fileLeaf, sXLength, sYLength, sZLength

                AddPicture  photosPath

                iRow = iRow + 1

                If objFSO.FileExists(mainDirectory & "\" & fileLeaf & ".stp") Then
                    objFSO.MoveFile  mainDirectory & "\" & fileLeaf & ".stp", stpDest
                End If

                If objFSO.FileExists(mainDirectory & "\" & fileLeaf & ".step") Then
                    objFSO.MoveFile  mainDirectory & "\" & fileLeaf & ".step", stpDest
                End If

                If objFSO.FileExists(mainDirectory & "\" & fileLeaf & ".catpart") Then
                    objFSO.MoveFile  mainDirectory & "\" & fileLeaf & ".catpart", catDest
                End If

                If objFSO.FileExists(mainDirectory & "\" & fileLeaf & ".igs") Then
                    objFSO.MoveFile  mainDirectory & "\" & fileLeaf & ".igs", igsDest
                End If

            End If

            CATIA.ActiveWindow.Close()
        End If

        Next
End Sub

Sub FindExtremes(myBodyPart, theHSF, theExtremums,  mins, maxs)
    Dim dCoords(2) as Object
    For ii = 0 To 5
        Set theEXRef = myBodyPart.CreateReferenceFromObject(theExtremums(ii))
        Set aPoint = theHSF.AddNewPointDatum(theEXRef)
        aPoint.Compute()
        aPoint.GetCoordinates(dCoords)
        For j = 0 To 2
            If dCoords(j) < mins(j) Then
                mins(j) = dCoords(j)
            End If
            If dCoords(j) > maxs(j) Then
                maxs(j) = dCoords(j)
            End If
            Next
            Next
End Sub

Sub SetExtremes(myBodyPart,theExtremums, theHSF, theObjectRef, theXDir, theYDir, theZDir, i, other)

    ' Construct some extremums and check the coordinates against the mins/maxs
    Set theExtremums(i) =theHSF.AddNewExtremum(theObjectRef, theXDir, other)
    theExtremums(i).Direction2 = theYDir
    theExtremums(i).ExtremumType2 = 1
    theExtremums(i).Direction3 = theZDir
    theExtremums(i).ExtremumType3 = 1
    myBodyPart.UpdateObject(theExtremums(i))

End Sub
Sub FillOut( fileName As String, fileLeaf As String, length As Integer, width As Integer, height As Integer)


    myExcel.Workbooks.Item(1).ActiveSheet.Cells(iRow, 18).RowHeight = 80

    myExcel.Workbooks.Item(1).ActiveSheet.Cells(iRow, 18).Value = fileLeaf & ".bmp"

    myExcel.Workbooks.Item(1).ActiveSheet.Cells(iRow, 18).Value = fileLeaf & ".bmp"

    myExcel.Workbooks.Item(1).ActiveSheet.Cells(iRow, 1).Value = iRow - 1

    myExcel.Workbooks.Item(1).ActiveSheet.Cells(iRow, 3).Value = fileName

    myExcel.Workbooks.Item(1).ActiveSheet.Cells(iRow, 4).Value = fileLeaf

    myExcel.Workbooks.Item(1).ActiveSheet.Cells(iRow, 6).Value = length

    myExcel.Workbooks.Item(1).ActiveSheet.Cells(iRow, 7).Value = width

    myExcel.Workbooks.Item(1).ActiveSheet.Cells(iRow, 8).Value = height
End Sub


Sub AddPicture(photosPath As String)

    Set oPicture = myExcel.ActiveSheet.Shapes.AddPicture(photosPath, False, True, 1, 1, 100, 75)
    With oPicture
        .Left = myExcel.ActiveSheet.Cells(iRow, 2).Left
        .Top = myExcel.ActiveSheet.Cells(iRow, 2).Top
        .Placement = 1
    End With

End Sub

' 468
